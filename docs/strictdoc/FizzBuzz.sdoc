[REQUIREMENT: REQ-001]
TITLE: Print numbers from 1 to 100
STATEMENT:
  The system shall print numbers from 1 to 100 sequentially.

[REQUIREMENT: REQ-002]
TITLE: Print Fizz for numbers divisible by three
STATEMENT:
  For numbers divisible by three, the system shall print "Fizz" instead of the number.

[REQUIREMENT: REQ-003]
TITLE: Print Buzz for numbers divisible by five
STATEMENT:
  For numbers divisible by five, the system shall print "Buzz" instead of the number.

[REQUIREMENT: REQ-004]
TITLE: Print FizzBuzz for numbers divisible by both three and five
STATEMENT:
  For numbers divisible by both three and five, the system shall print "FizzBuzz" instead of the number.
